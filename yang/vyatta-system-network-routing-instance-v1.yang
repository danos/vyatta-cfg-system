module vyatta-system-network-routing-instance-v1 {
	namespace "urn:vyatta.com:mgmt:vyatta-system-network-routing-instance:1";
	prefix vyatta-system-network-routing-instance-v1;

	import configd-v1 {
		prefix configd;
	}
	import vyatta-routing-v1 {
		prefix rt-instance;
	}
	import vyatta-system-network-v1 {
		prefix sys-network;
	}

	organization "AT&T Inc.";
	contact
		"AT&T
		 Postal: 208 S. Akard Street
		         Dallas, TX 75202
		 Web: www.att.com";

	description
		"Copyright (c) 2019, AT&T Intellectual Property.
		 All rights reserved.

		 Copyright (c) 2016 by Brocade Communications Systems, Inc.
		 All rights reserved.

		 Redistribution and use in source and binary forms, with or without
		 modification, are permitted provided that the following conditions
		 are met:

		 1. Redistributions of source code must retain the above copyright
		    notice, this list of conditions and the following disclaimer.
		 2. Redistributions in binary form must reproduce the above
		    copyright notice, this list of conditions and the following
		    disclaimer in the documentation and/or other materials provided
		    with the distribution.
		 3. Neither the name of the copyright holder nor the names of its
		    contributors may be used to endorse or promote products derived
		    from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 The YANG module for vyatta-system-network-routing-instance-v1";

	revision 2019-11-21 {
		description "Update system static-host-mapping actions";
	}

	revision 2016-05-31 {
		description "Support DNS subset of system-network.";
	}

	revision 2016-04-18 {
		description "VRF support for DNS domain.";
	}

	augment /rt-instance:routing/rt-instance:routing-instance/rt-instance:system {
		uses sys-network:system-network-domain {
			refine domain-name {
				description "Configure domain name for dns resolver in routing instance";
				configd:update "/opt/vyatta/share/tmplscripts/system/domain-name/configd_update.sh --vrf=$VAR(../../@)";
				configd:delete "/opt/vyatta/share/tmplscripts/system/domain-name/configd_delete.sh --vrf=$VAR(../../@)";
			}
			refine domain-search {
				description "Search list for host-name lookup in routing instance";
			}
			refine domain-search/domain {
				description "Domain name in search order for routing instance";
				configd:create "/opt/vyatta/share/tmplscripts/system/domain-search/domain/configd_create2";
				configd:delete "/opt/vyatta/share/tmplscripts/system/domain-search/domain/configd_delete2";
			}
		}
		uses sys-network:system-network-name-server-static-hosts {
			refine name-server {
				description "Name server list for domain lookup in routing instance";
				configd:create "/opt/vyatta/share/tmplscripts/system/name-server/configd_create2";
				configd:delete "/opt/vyatta/share/tmplscripts/system/name-server/configd_delete2";
			}
			refine static-host-mapping {
				configd:end "/opt/vyatta/sbin/vyatta_static_host_mapping --vrf=$VAR(../../@)";
			}
			refine static-host-mapping/host-name/inet {
				mandatory "true";
			}                       
		}
	}                       
}
