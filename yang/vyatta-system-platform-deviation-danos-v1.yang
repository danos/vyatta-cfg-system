module vyatta-system-platform-deviation-danos-v1 {
	namespace "urn:vyatta.com:mgmt:vyatta-system-platform-deviation-danos:1";
	prefix vyatta-system-platform-deviation-danos-v1;

	import vyatta-system-v1 {
		prefix system;
	}

	import vyatta-system-platform-v1 {
		prefix platf;
	}

	import configd-v1 {
		prefix configd;
	}

    organization "AT&T Inc.";
	contact
		"AT&T
          Postal: 208 S. Akard Street
                  Dallas, TX 75202
          Web: www.att.com";

	description
		"Copyright (c) 2019-2020, AT&T Intellectual Property.
		 All rights reserved.

		 Redistribution and use in source and binary forms, with or without
		 modification, are permitted provided that the following conditions
		 are met:

		 1. Redistributions of source code must retain the above copyright
		    notice, this list of conditions and the following disclaimer.
		 2. Redistributions in binary form must reproduce the above
		    copyright notice, this list of conditions and the following
		    disclaimer in the documentation and/or other materials provided
		    with the distribution.
		 3. Neither the name of the copyright holder nor the names of its
		    contributors may be used to endorse or promote products derived
		    from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

         Deviations for platform types on DANOS.";

	revision 2020-07-01 {
		description "Deviation requires explicit enumeration as some
                     clients are unable to properly process file-scoped
                     typedefs.";
	}

	revision 2019-11-13 {
		description "Initial revision.";
	}

	typedef platform-type-danos {
		type enumeration {
			enum "switch" {
				configd:help "Switch interfaces enslaved to hardware switches by default.";
				description
					"The platform is configured as a switch. Interfaces
                     belonging to a hardware switch are automatically enslaved
                     to the appropriate switch by default";
			}
		}
	}

	deviation /system:system/platf:platform/platf:type {
		description
			"DANOS only supports the switch platform type.";
		deviate replace {
			type enumeration {
				enum "switch" {
					configd:help "Switch interfaces enslaved to hardware switches by default.";
					description
						"The platform is configured as a switch. Interfaces
						 belonging to a hardware switch are automatically
						 enslaved to the appropriate switch by default";
				}
			}
		}
	}
}
