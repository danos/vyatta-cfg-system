module vyatta-system-misc-v1 {
	namespace "urn:vyatta.com:mgmt:vyatta-system-misc:1";
	prefix vyatta-system-misc-v1;

	import vyatta-system-v1 {
		prefix system;
	}
	import configd-v1 {
		prefix configd;
	}

	organization "AT&T Inc.";
	contact
		"AT&T
		Postal: 208 S. Akard Street
			Dallas, TX 75202
		Web: www.att.com";

        description
		"Copyright (c) 2018-2020 AT&T Intellectual Property
		 All rights reserved.

		 Copyright (c) 2014-2016 by Brocade Communications Systems, Inc.
		 All rights reserved.

		 Redistribution and use in source and binary forms, with or without
		 modification, are permitted provided that the following conditions
		 are met:

		 1. Redistributions of source code must retain the above copyright
		    notice, this list of conditions and the following disclaimer.
		 2. Redistributions in binary form must reproduce the above
		    copyright notice, this list of conditions and the following
		    disclaimer in the documentation and/or other materials provided
		    with the distribution.
		 3. Neither the name of the copyright holder nor the names of its
		    contributors may be used to endorse or promote products derived
		    from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 Miscellaneous system configuration";

	revision 2020-02-19 {
		description "Add configuration for NMI and panic behaviors.";
	}

	revision 2018-12-18 {
		description "Remove variable expansion from error message.";
	}

	revision 2018-07-24 {
		description "Remove stub template script.
			     Update copyright and contact.";
	}

	revision 2016-03-02 {
		description "serial-boot-console added";
	}

	revision 2015-08-14 {
		description "Initial revision of version 1.";
	}

	augment /system:system {
		container console {
			presence "true";
			configd:priority "100";
			configd:help "Serial console configuration";
			configd:end "vyatta_update_console.pl";
			leaf serial-boot-console {
				description "This serial console will be used for boot messages."
					+ " If this does not exist then tty0 will be used";
				configd:help "Serial console to use for boot messages";
				type leafref {
					path "../device/tagnode";
				}
				must "not (../device[tagnode=current()]/modem)"{
					error-message "boot-console cannot be a modem console";
				}
			}
			leaf powersave {
				type empty;
				configd:help "Enable screen blank powersaving on VGA console";
				configd:create "/opt/vyatta/share/tmplscripts/system/console/powersave/configd_create.sh";
				configd:delete "/opt/vyatta/share/tmplscripts/system/console/powersave/configd_delete.sh";
			}
			list device {
				configd:help "Serial console device name";
				configd:end "/opt/vyatta/share/tmplscripts/system/console/device/configd_end.sh";
				key "tagnode";
				leaf tagnode {
					type string {
						pattern '((tty[A-Z])|ttyUSB|(hvc)){1}[0-9]+';
					}
					configd:help "Serial console device name";
				}
				leaf modem {
					type empty;
					configd:help "Device is Hayes compatible modem";
				}
				leaf speed {
					type enumeration {
						enum "1200" {
							configd:help "1200 bps";
						}
						enum "2400" {
							configd:help "2400 bps";
						}
						enum "4800" {
							configd:help "4800 bps";
						}
						enum "9600" {
							configd:help "9600 bps (default)";
						}
						enum "19200" {
							configd:help "19,200 bps";
						}
						enum "38400" {
							configd:help "38,400 bps";
						}
						enum "57600" {
							configd:help "57,600 bps";
						}
						enum "115200" {
							configd:help "115,200 bps";
						}
					}
					configd:help "Console baud rate";
					default "9600";
					configd:allowed "/opt/vyatta/share/tmplscripts/system/console/device/speed/configd_allowed.sh";
				}
			}
		}

		container fault-behavior {
			configd:help "Configure responses to software and hardware exceptions";
			description "These options allow the end user to configure the response
				     to unusual hardware and software exceptions. This is
				     typically used to evoke a well-defined behavior in the
				     event of these failures.";

			leaf panic-on-io-nmi {
				type boolean;
				configd:help "Panic kernel when unexpected I/O NMI occurs.";
				description "Panic kernel when unexpected I/O NMI occurs.";
				default "false";
				configd:end 'sysctl -q -w kernel.panic_on_io_nmi=$(if [ $VAR(@) == "true" ]; then echo 1; else echo 0; fi)';
			}

			leaf panic-on-oom {
				type boolean;
				configd:help "Panic kernel when an out-of-memory condition occurs.";
				description "Panic kernel when an out-of-memory condition occurs.";
				default "false";
				configd:end 'sysctl -q -w vm.panic_on_oom=$(if [ $VAR(@) == "true" ]; then echo 1; else echo 0; fi)';
			}

			leaf panic-on-oops {
				type boolean;
				configd:help "Panic kernel when encountering an oops or BUG.";
				description "Panic kernel when encountering an oops or BUG.";
				default "true";
				configd:end 'sysctl -q -w kernel.panic_on_oops=$(if [ $VAR(@) == "true" ]; then echo 1; else echo 0; fi)';
			}

			leaf panic-on-unknown-nmi {
				type boolean;
				configd:help "Panic kernel when an unknown NMI occurs.";
				description "Panic kernel when an unknown NMI occurs.";
				default "false";
				configd:end 'sysctl -q -w kernel.unknown_nmi_panic=$(if [ $VAR(@) == "true" ]; then echo 1; else echo 0; fi)';
			}

			leaf panic-on-unrecovered-nmi {
				type boolean;
				configd:help "Panic kernel when an unrecoverable NMI occurs.";
				description "Panic kernel when an unrecoverable NMI occurs.";
				default "false";
				configd:end 'sysctl -q -w kernel.panic_on_unrecovered_nmi=$(if [ $VAR(@) == "true" ]; then echo 1; else echo 0; fi)';
			}

			leaf reboot-on-panic {
				type boolean;
				configd:help "Reboot system on kernel panic";
				default "true";
				configd:end 'sysctl -q -w kernel.panic=$(if [ "$VAR(../../options/reboot-on-panic/@)" != "false" -a $VAR(@) == "true" ]; then echo $VAR(../reboot-wait-after-panic/@); else echo 0; fi)';
			}

			leaf reboot-wait-after-panic {
				type uint32 {
					range 1..2147483647;
				}
				configd:help "The number of seconds to wait before rebooting after a panic.";
				description "The number of seconds to wait before rebooting after a panic.";
				default "60";
				configd:end 'sysctl -q -w kernel.panic=$(if [ "$VAR(../../options/reboot-on-panic/@)" != "false" -a $VAR(../reboot-on-panic/@) == "true" ]; then echo $VAR(@); else echo 0; fi)';
			}
		}

		container options {
			presence "true";
			configd:priority "400";
			configd:help "System options";
			status deprecated;

			leaf reboot-on-panic {
				type boolean;
				configd:help "Reboot system on kernel panic";
				default "true";
				configd:update 'sysctl -q -w kernel.panic=$(if [ $VAR(@) == "true" ]; then echo $VAR(../../fault-behavior/reboot-wait-after-panic/@); else echo 0; fi)';
				configd:delete 'sysctl -q -w kernel.panic=$(if [ "$VAR(../../fault-behavior/reboot-on-panic/@)" == "true" ]; then echo $VAR(../../fault-behavior/reboot-wait-after-panic/@); else echo 0; fi)';
			}
		}
	}
}
