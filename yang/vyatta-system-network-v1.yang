module vyatta-system-network-v1 {
	namespace "urn:vyatta.com:mgmt:vyatta-system-network:1";
	prefix vyatta-system-network-v1;

	import vyatta-types-v1 {
		prefix types;
	}
	import vyatta-system-v1 {
		prefix system;
	}
	import configd-v1 {
		prefix configd;
	}

	organization "AT&T Inc.";
	contact
		"AT&T
		 Postal: 208 S. Akard Street
		         Dallas, TX 75202
		 Web: www.att.com";

	description
		"Copyright (c) 2017-2021 AT&T Intellectual Property
		 All rights reserved.

		 Copyright (c) 2014-2016 by Brocade Communications Systems, Inc.
		 All rights reserved.

		 Redistribution and use in source and binary forms, with or without
		 modification, are permitted provided that the following conditions
		 are met:

		 1. Redistributions of source code must retain the above copyright
		    notice, this list of conditions and the following disclaimer.
		 2. Redistributions in binary form must reproduce the above
		    copyright notice, this list of conditions and the following
		    disclaimer in the documentation and/or other materials provided
		    with the distribution.
		 3. Neither the name of the copyright holder nor the names of its
		    contributors may be used to endorse or promote products derived
		    from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 Global network parameter configuration";

	revision 2021-10-18 {
		description "Modify ipv6 sysctl settings without altering default
			     settings of startup config file.";
	}
	revision 2021-07-14 {
		description "Add configuration for TOS(ICMPv4 and ESP).
			     Add configuration for TCLASS(ICMPv6, ND, ESP).";
	}

	revision 2021-06-11 {
		description "Add ICMP rate limiting operational model.";
	}

	revision 2021-05-22 {
		description "Add ICMP keyword.";
	}

	revision 2021-03-15 {
		description "Clarify that removal of ARP entries by the garbage collector
			     in the control plane depends not only on cache timeout, but also
			     on how many entries are present if cache size is configured.";
	}

	revision 2020-11-19 {
		description "Add configuration for ARP cache size and ARP cache timeout.
			     Allow ND table size of 128K entries.
			     Modify actions for ND.";
	}

	revision 2020-08-07 {
		description "Remove default host-name";
	}

	revision 2019-11-21 {
		description "Update system static-host-mapping actions";
	}

	revision 2019-10-15 {
		description "Allow ND table size of 64K entries";
	}

	revision 2019-09-04 {
		description "Add delete action for ND table size";
	}

	revision 2019-09-03 {
		description "Add configuration for ND resolution throttling";
	}

	revision 2019-08-29 {
		description "Modify update action for gratuitous arp";
	}

	revision 2018-12-18 {
		description "Remove DNS forwarding hook.
			     Remove variable expansions from error messages.";
	}

	revision 2018-07-02 {
		description "Add ICMP/ND redirect disable/enable capability";
	}

	revision 2018-06-15 {
		description "Support for gratuitous ARP processing";
	}
	revision 2018-04-30 {
		description "Add static-host-mapping script";
	}

	revision 2017-09-07 {
		description "Deprecate the arp command";
	}

	revision 2016-05-31 {
		description "Split grouping for system network.";
	}

	revision 2016-04-18 {
		description "Add grouping for system network.";
	}

	revision 2015-08-14 {
		description "Initial revision of version 1.";
	}

	grouping system-network-domain {
		leaf domain-name {
			type types:domain-name;
			configd:priority "400";
			configd:help "System domain name";
			configd:update "/opt/vyatta/share/tmplscripts/system/domain-name/configd_update.sh";
			configd:delete "/opt/vyatta/share/tmplscripts/system/domain-name/configd_delete.sh";
		}
		container domain-search {
			presence "true";
			configd:priority "400";
			configd:help "Domain Name Server (DNS) domain completion order";
			leaf-list domain {
				type string {
					pattern '[-a-zA-Z0-9\.]+';
				}
				ordered-by "user";
				configd:help "DNS domain completion order";
				configd:create "/opt/vyatta/share/tmplscripts/system/domain-search/domain/configd_create1.cli";
				configd:delete "/opt/vyatta/share/tmplscripts/system/domain-search/domain/configd_delete1.cli";
			}
		}
	}

	typedef garp-packet-action {
		type enumeration {
			enum "drop" {
				configd:help "Drop specified packets";
				description "Drop specified packets";
			}
			enum "update" {
				configd:help "Accept GARP packets for known L3 addresses";
				description "Accept GARP packets for known L3 addresses. Update mac address binding only for
                                             ARP entries that already exist. No new ARP entries are created";
			}
		}
	}

	grouping garp-config {
		container gratuitous-arp {
			description "Gratuitous ARP processing control";
			configd:help "Gratuitous ARP processing control";
			leaf request {
				description "Action to take on GARP Request packets";
				configd:help "Action to take on GARP Request packets";
				type garp-packet-action;
			}
			leaf reply {
				description "Action to take on GARP Reply packets";
				configd:help "Action to take on GARP Reply packets";
				type garp-packet-action;
			}
		}
	}

	typedef table-size-enumeration {
		type enumeration {
			enum "1024" {
				configd:help "entries";
			}
			enum "2048" {
				configd:help "entries";
			}
			enum "4096" {
				configd:help "entries";
			}
			enum "8192" {
				configd:help "entries";
			}
			enum "16384" {
				configd:help "entries";
			}
			enum "32768" {
				configd:help "entries";
			}
			enum "65536" {
				configd:help "entries";
			}
			enum "131072" {
				configd:help "entries";
			}
		}
	}

	grouping icmp-rate-limit-counters {
		leaf limit {
			description "Maximum rate";
			type uint32 {
				range 0..1000;
			}
		}

		leaf sent {
			description "Total ICMP packets sent";
			type uint32;
		}

		leaf dropped {
			description "ICMP packets dropped in total";
			type uint32;
		}

		leaf dropped-1-min {
			description "ICMP packets dropped in previous 1 minute";
			type uint32;
		}

		leaf dropped-3-min {
			description "ICMP packets dropped in previous 3 minutes";
			type uint32;
		}

		leaf dropped-5-min {
			description "ICMP packets dropped in previous 5 minutes";
			type uint32;
		}
	}

	typedef service-class {
		type string {
			pattern "0x[0-9a-fA-F]{1,2}";
			configd:pattern-help "<0x00-0xFF>";
		}
		description "The service-class type represents a one byte hex value.
			     service-class represents the traffic class field in IPv6 packet
			     and type of service field in IPv4 packet.";
	}

	grouping system-network-hostname-ipinfo {
		configd:end "vyatta-ipv6-conf";
		leaf host-name {
			type string {
				pattern '[0-9A-Za-z][-\.0-9A-Za-z]*[0-9A-Za-z]';
				length "2..63";
			}
			configd:priority "100";
			configd:help "System host name";
			configd:update "/opt/vyatta/share/tmplscripts/system/host-name/configd_update.sh";
			configd:delete "/opt/vyatta/share/tmplscripts/system/host-name/configd_delete.sh";
		}
		container ip {
			presence "true";
			configd:priority "400";
			configd:help "IPv4 settings";
			container arp {
				configd:help "Parameters for ARP cache";
				configd:end "/opt/vyatta/sbin/vyatta-update-arp-params --action=${COMMIT_ACTION}";
				leaf table-size {
					type table-size-enumeration;
					description "Maximum number of entries in ARP cache.
						     Defaults: control plane: 1024, dataplane: 'unlimited'";
					configd:help "Maximum number of entries in ARP cache (defaults: control plane: 1024, dataplane: 'unlimited')";
				}
				leaf stale-time {
					type uint32 {
						range 30..21474836;
						configd:help "time (in seconds)";
					}
					units seconds;
					description "Expiry time for stale entries in ARP cache.
						     How long entries remain in control plane cache also
						     depends on how many are present if table size is set.
						     Defaults: control plane: 60s, dataplane: 1200s";
					configd:help "Expiry time for stale entries in ARP cache (defaults: control plane [conditional]: 60s, dataplane: 1200s)";
				}
			}
			container icmp {
				configd:help "Parameters for generated ICMP rate limiting";
				presence "ICMP rate limit feature configured";
				container rate-limit {
					configd:help "Maximum messages per second";
					container type {
						configd:help "ICMP type to rate limit on generation";
						description "ICMP type to rate limit";
						leaf time-exceeded {
							configd:help "ICMP TTL expired";
							type uint32 {
								range 1..1000;
								configd:help "Maximum messages generated per second";
							}
							configd:update "/opt/vyatta/sbin/vyatta-icmp-rate-limit --action=SET --param=maximum --prot=ICMPV4 --type=$VAR(.) --maximum=$VAR(@)";
							configd:delete "/opt/vyatta/sbin/vyatta-icmp-rate-limit --action=DELETE --param=maximum --prot=ICMPV4 --type=$VAR(.) --maximum=$VAR(@)";
						}
						leaf destination-unreachable {
							configd:help "ICMP Destination Unreachable";
							type uint32 {
								range 1..1000;
								configd:help "Maximum messages generated per second";
							}
							configd:update "/opt/vyatta/sbin/vyatta-icmp-rate-limit --action=SET --param=maximum --prot=ICMPV4 --type=$VAR(.) --maximum=$VAR(@)";
							configd:delete "/opt/vyatta/sbin/vyatta-icmp-rate-limit --action=DELETE --param=maximum --prot=ICMPV4 --type=$VAR(.) --maximum=$VAR(@)";
						}
						leaf redirect {
							configd:help "ICMP Redirect";
							type uint32 {
								range 1..1000;
								configd:help "Maximum messages generated per second";
							}
							configd:update "/opt/vyatta/sbin/vyatta-icmp-rate-limit --action=SET --param=maximum --prot=ICMPV4 --type=$VAR(.) --maximum=$VAR(@)";
							configd:delete "/opt/vyatta/sbin/vyatta-icmp-rate-limit --action=DELETE --param=maximum --prot=ICMPV4 --type=$VAR(.) --maximum=$VAR(@)";
						}
					}
					leaf default {
						description "All ICMP types not explicitly configured for rate limit";
						configd:help "All ICMP types not explicitly configured for rate limit";
						type uint32 {
							range 1..1000;
							configd:help "Maximum messages generated per second";
						}
						configd:update "/opt/vyatta/sbin/vyatta-icmp-rate-limit --action=SET --param=maximum --prot=ICMPV4 --type=$VAR(.) --maximum=$VAR(@)";
						configd:delete "/opt/vyatta/sbin/vyatta-icmp-rate-limit --action=DELETE --param=maximum --prot=ICMPV4 --type=$VAR(.) --maximum=$VAR(@)";
					}
					container state {
						config false;
						configd:get-state "vyatta-icmp-rate-limit-state --af=v4";

						list icmp-types {
							description "Rate limited ICMP types";
							key icmp-type;

							leaf icmp-type {
								type enumeration {
									enum destination-unreachable {
										description "Destination unreachable";
									}
									enum time-exceeded {
										description "Time To Live expired";
									}
									enum redirect {
										description "Redirect";
									}
								}
							}

							uses icmp-rate-limit-counters;
						}
					}
				}
			}
			leaf disable-forwarding {
				type empty;
				configd:help "Disable IPv4 forwarding";
				configd:create "/opt/vyatta/share/tmplscripts/system/ip/disable-forwarding/configd_create.sh";
				configd:delete "/opt/vyatta/share/tmplscripts/system/ip/disable-forwarding/configd_delete.sh";
			}
			uses garp-config {
				refine gratuitous-arp {
					configd:help "Global processing behaviour for gratuitous ARPs";
					description "Global processing behaviour for gratuitous ARPs";
				}
				refine gratuitous-arp/request {
					configd:update "/opt/vyatta/sbin/vyatta-interfaces-garp --action ${COMMIT_ACTION} --garp $VAR(.),$VAR(@)";
					configd:delete "/opt/vyatta/sbin/vyatta-interfaces-garp --action ${COMMIT_ACTION} --garp $VAR(.),$VAR(@)";
				}
				refine gratuitous-arp/reply {
					configd:update "/opt/vyatta/sbin/vyatta-interfaces-garp --action ${COMMIT_ACTION} --garp $VAR(.),$VAR(@)";
					configd:delete "/opt/vyatta/sbin/vyatta-interfaces-garp --action ${COMMIT_ACTION} --garp $VAR(.),$VAR(@)";
				}
			}
			leaf disable-redirects {
				type empty;
				configd:help "Disable IPv4 ICMP redirects";
				configd:create "/opt/vyatta/share/tmplscripts/system/ip/disable-redirects/configd_create.sh";
				configd:delete "/opt/vyatta/share/tmplscripts/system/ip/disable-redirects/configd_delete.sh";
			}
			container icmp-error {
				description "Assign forwarding class to ICMPv4 error packets.";
				configd:help "TOS value to be used when dataplane sending ICMP error packets.";
				leaf tos {
					type service-class;
					description "Dataplane creates the ICMPv4 error messages with TOS value
						     and sends the control packet out.";
					configd:help "Type of Service (TOS)";
					default "0xC0";
					configd:update "ForwardingClassConfig --action=SET --cmd=tos_tclass_config --proto=icmp --value=$VAR(@) --ip=ipv4";
					configd:delete "ForwardingClassConfig --action=DELETE --cmd=tos_tclass_config --proto=icmp --value=$VAR(@) --ip=ipv4";
				}
			}
			container esp {
				description "Assign forwarding class to ESP packets.";
				configd:help "TOS value to be used when sending IPsec IPv4 packet";
				leaf tos {
					type union {
						type enumeration {
							enum "inherit" {
								configd:help "Inherit from original IP header";
							}
						}
						type service-class;
					}
					description "IPsec IPv4 packets goes out with given TOS value.
						     By default Dataplane creates a packet with TOS inherited from
						     orignal IP header.";
					configd:help "Type of Service (TOS)";
					default "inherit";
					configd:update "ForwardingClassConfig --action=SET --cmd=tos_tclass_config --proto=esp --value=$VAR(@) --ip=ipv4";
					configd:delete "ForwardingClassConfig --action=DELETE --cmd=tos_tclass_config --proto=esp --value=$VAR(@) --ip=ipv4";
				}
			}
		}
		container ipv6 {
			presence "true";
			configd:help "IPv6 settings";
			leaf disable {
				type empty;
				configd:priority "400";
				configd:help "Disable assignment of IPv6 addresses on all interfaces";
			}
			leaf strict-dad {
				type empty;
				configd:priority "290";
				configd:help "Disable IPv6 operation on interface when DAD fails on LL addr";
				configd:create "/opt/vyatta/share/tmplscripts/system/ipv6/strict-dad/configd_create.sh";
				configd:delete "/opt/vyatta/share/tmplscripts/system/ipv6/strict-dad/configd_delete.sh";
			}
			container neighbor {
				presence "true";
				configd:priority "400";
				configd:help "Parameters for Neighbor cache";
				leaf table-size {
					type table-size-enumeration;
					configd:help "Maximum number of entries to keep in the Neighbor cache (default: 8192)";
					default "8192";
					configd:update "/opt/vyatta/sbin/vyatta-update-arp-params --action=SET --param=table-size --value=$VAR(@) --ipv6";
					configd:delete "/opt/vyatta/sbin/vyatta-update-arp-params --action=DELETE --param=table-size --value=$VAR(@) --ipv6";
				}
				leaf resolution-throttling {
					type int16 {
						range 1..32767;
						configd:help "Value to set resolution throttling to";
					}
					description "Maximum number of pending resolutions";
					configd:help "Maximum number of pending resolutions (default: 100)";
					configd:update "/opt/vyatta/sbin/vyatta-update-arp-params --action=SET --param=resolution-throttling --value=$VAR(@) --ipv6";
					configd:delete "/opt/vyatta/sbin/vyatta-update-arp-params --action=DELETE --param=resolution-throttling --value=$VAR(@) --ipv6";
				}
			}
			container icmp {
				configd:help "Parameters for generated ICMPv6 rate limiting";
				presence "ICMP rate limit feature is configured";
				container rate-limit {
					configd:help "Maximum messages per second";
					container type {
						configd:help "ICMPv6 type to rate limit on generation";
						description "ICMPv6 type to rate limit";
						leaf time-exceeded {
							configd:help "ICMPv6 TTL expired";
							type uint32 {
								range 1..1000;
								configd:help "Maximum messages generated per second";
							}
							configd:update "/opt/vyatta/sbin/vyatta-icmp-rate-limit --action=SET --param=maximum --prot=ICMPV6 --type=$VAR(.) --maximum=$VAR(@)";
							configd:delete "/opt/vyatta/sbin/vyatta-icmp-rate-limit --action=DELETE --param=maximum --prot=ICMPV6 --type=$VAR(.) --maximum=$VAR(@)";
						}
						leaf destination-unreachable {
							configd:help "ICMPv6 Destination Unreachable";
							type uint32 {
								range 1..1000;
								configd:help "Maximum messages generated per second";
							}
							configd:update "/opt/vyatta/sbin/vyatta-icmp-rate-limit --action=SET --param=maximum --prot=ICMPV6 --type=$VAR(.) --maximum=$VAR(@)";
							configd:delete "/opt/vyatta/sbin/vyatta-icmp-rate-limit --action=DELETE --param=maximum --prot=ICMPV6 --type=$VAR(.) --maximum=$VAR(@)";
						}
						leaf too-big {
							configd:help "ICMPv6 Too Big";
							type uint32 {
								range 1..1000;
								configd:help "Maximum messages generated per second";
							}
							configd:update "/opt/vyatta/sbin/vyatta-icmp-rate-limit --action=SET --param=maximum --prot=ICMPV6 --type=$VAR(.) --maximum=$VAR(@)";
							configd:delete "/opt/vyatta/sbin/vyatta-icmp-rate-limit --action=DELETE --param=maximum --prot=ICMPV6 --type=$VAR(.) --maximum=$VAR(@)";
						}
						leaf parameter-problem {
							configd:help "ICMPv6 Parameter Problem";
							type uint32 {
								range 1..1000;
								configd:help "Maximum messages generated per second";
							}
							configd:update "/opt/vyatta/sbin/vyatta-icmp-rate-limit --action=SET --param=maximum --prot=ICMPV6 --type=$VAR(.) --maximum=$VAR(@)";
							configd:delete "/opt/vyatta/sbin/vyatta-icmp-rate-limit --action=DELETE --param=maximum --prot=ICMPV6 --type=$VAR(.) --maximum=$VAR(@)";
						}
					}
					leaf default {
						description "All ICMP types not explicitly configured for rate limit";
						configd:help "All ICMP types not explicitly configured for rate limit";
						type uint32 {
							range 1..1000;
							configd:help "Maximum messages generated per second";
						}
						configd:update "/opt/vyatta/sbin/vyatta-icmp-rate-limit --action=SET --param=maximum --prot=ICMPV6 --type=$VAR(.) --maximum=$VAR(@)";
						configd:delete "/opt/vyatta/sbin/vyatta-icmp-rate-limit --action=DELETE --param=maximum --prot=ICMPV6 --type=$VAR(.) --maximum=$VAR(@)";
					}
					container state {
						config false;
						configd:get-state "vyatta-icmp-rate-limit-state --af=v6";

						list icmp-types {
							description "Rate limited ICMPv6 types";
							key icmp-type;

							leaf icmp-type {
								type enumeration {
									enum destination-unreachable {
										description "Destination unreachable";
									}
									enum time-exceeded {
										description "Time To Live expired";
									}
									enum too-big {
										description "Too big to fragment";
									}
									enum parameter-problem {
										description "Parameter problem";
									}
								}
							}

							uses icmp-rate-limit-counters;
						}
					}
				}
			}
			leaf disable-forwarding {
				type empty;
				configd:priority "400";
				configd:help "Disable IPv6 forwarding on all interfaces";
				configd:create "/opt/vyatta/share/tmplscripts/system/ipv6/disable-forwarding/configd_create.sh";
				configd:delete "/opt/vyatta/share/tmplscripts/system/ipv6/disable-forwarding/configd_delete.sh";
			}
			leaf disable-redirects {
			     type empty;
			     configd:help "Disable IPv6 ND redirects";
			     configd:create "ip6_disable_redirects --action=true";
			     configd:delete "ip6_disable_redirects --action=false";
			}
			container icmpv6-error {
				description "Assign forwarding class to ICMPv6-error packets.";
				configd:help "Tclass value to be used when dataplane sending ICMPv6 error packets.";
				leaf tclass {
					type service-class;
					description "Dataplane creates the ICMPv6 error messages with tclass value
						     and sends the control packet out.";
					configd:help "Traffic class (Tclass)";
					default "0xC0";
					configd:update "ForwardingClassConfig --action=SET --cmd=tos_tclass_config --proto=icmp --value=$VAR(@) --ip=ipv6";
					configd:delete "ForwardingClassConfig --action=DELETE --cmd=tos_tclass_config --proto=icmp --value=$VAR(@) --ip=ipv6";
				}
			}
			container nd {
				description "Assign forwarding class to ND packets.";
				configd:help "Tclass value to be used when dataplane sending ND packets.";
				leaf tclass {
					type service-class;
					configd:help "Traffic class (Tclass)";
					description "Dataplane creates the neighbor discovery packets for all
						     types with tclass value and sends the packet out.";
					default "0xC0";
					configd:update "ForwardingClassConfig --action=SET --cmd=tos_tclass_config --proto=nd --value=$VAR(@) --ip=ipv6";
					configd:delete "ForwardingClassConfig --action=DELETE --cmd=tos_tclass_config --proto=nd --value=$VAR(@) --ip=ipv6";
				}
			}
			container esp {
				description "Assign forwarding class to ESP packets.";
				configd:help "Tclass value to be used when sending IPsec IPv6 packet";
				leaf tclass {
					type union {
						type enumeration {
							enum "inherit" {
								configd:help "Inherit from original IP header";
							}
						}
						type service-class;
					}
					description "IPsec IPv6 packets goes out with given tclass value.
						     By default Dataplane creates a packet with tclass inherited from
						     orignal IP header.";
					configd:help "Traffic class (Tclass)";
					default "inherit";
					configd:update "ForwardingClassConfig --action=SET --cmd=tos_tclass_config --proto=esp --value=$VAR(@) --ip=ipv6";
					configd:delete "ForwardingClassConfig --action=DELETE --cmd=tos_tclass_config --proto=esp --value=$VAR(@) --ip=ipv6";
				}
			}
		}
	}

	grouping system-network-name-server-static-hosts {
		leaf-list name-server {
			type union {
				type types:ipv4-address;
				type types:ipv6-address;
			}
			ordered-by "user";
			configd:priority "400";
			configd:help "Domain Name Server (DNS)";
			configd:create "/opt/vyatta/share/tmplscripts/system/name-server/configd_create.sh";
			configd:delete "/opt/vyatta/share/tmplscripts/system/name-server/configd_delete.sh";
		}
		container static-host-mapping {
			presence "true";
			configd:priority "400";
			configd:help "Map host names to addresses";
			configd:end "/opt/vyatta/sbin/vyatta_static_host_mapping";
			list host-name {
				configd:help "Host name for static address mapping";
				key "tagnode";
				leaf tagnode {
					type string {
						pattern '[0-9A-Za-z][-\.0-9A-Za-z]*[0-9A-Za-z]';
					}
					configd:help "Host name for static address mapping";
				}
				leaf inet {
					type union {
						type types:ipv4-address;
						type types:ipv6-address;
					}
					mandatory true;
					configd:help "Address [REQUIRED]";
				}
				leaf-list alias {
					type string {
						pattern '[0-9A-Za-z][-\.0-9A-Za-z]*[0-9A-Za-z]';
					}
					ordered-by "user";
					configd:help "Alias for this address";
				}
			}
		}
	}

	augment /system:system {
		uses system-network-domain;
		uses system-network-hostname-ipinfo;
		uses system-network-name-server-static-hosts;
	}
}
