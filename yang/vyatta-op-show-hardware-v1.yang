module vyatta-op-show-hardware-v1 {
	namespace "urn:vyatta.com:mgmt:vyatta-op-show-hardware:1";
	prefix vyatta-op-show-hardware-v1;

	import vyatta-opd-extensions-v1 {
		prefix opd;
	}
	import vyatta-op-show-v1 {
		prefix show;
	}

	organization "AT&T Inc.";
	contact
		"AT&T
		 Postal: 208 S. Akard Street
				 Dallas, TX 75202
		 Web: www.att.com";

	description
		"Copyright (c) 2018-2019, AT&T Intellectual Property.
		 All rights reserved.

		 Redistribution and use in source and binary forms, with or without
		 modification, are permitted provided that the following conditions
		 are met:

		 1. Redistributions of source code must retain the above copyright
		    notice, this list of conditions and the following disclaimer.
		 2. Redistributions in binary form must reproduce the above
		    copyright notice, this list of conditions and the following
		    disclaimer in the documentation and/or other materials provided
		    with the distribution.
		 3. Neither the name of the copyright holder nor the names of its
		    contributors may be used to endorse or promote products derived
		    from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		Defines the 'hardware' level under the 'show' command for operational CLI";

	revision 2019-03-23 {
		description "Add show command for hardware field-replaceable unit (FRU)";
	}
	revision 2018-07-12 {
		description "Add show commands for sensor system event logs (sel) and theshold";
	}

	revision 2018-06-19 {
		description "Initial version";
	}

	opd:augment /show:show {
		opd:command hardware {
			opd:help "Show system hardware details";

			opd:command dmi {
				opd:help "Show system DMI details";
				opd:on-enter 'vyatta-show-dmi';
			}

			opd:command fru {
				opd:help "Show system field-replaceable unit (FRU) details";
				opd:on-enter 'vyatta-show-fru';
			}

			opd:command mem {
				opd:help "Show system RAM details";
				opd:on-enter 'cat /proc/meminfo';
			}

			opd:command pci {
				opd:help "Show system PCI bus details";
				opd:on-enter 'lspci';

				opd:command detailed {
					opd:help "Show verbose system PCI bus details";
					opd:on-enter 'lspci -vvv';
				}
			}

			opd:command sensor {
				opd:help "Show sensors information";
				opd:on-enter 'vyatta-show-sensors sensor';
				opd:command sel {
					opd:help "Show sensor system event logs";
					opd:on-enter 'vyatta-show-sensors sel';
				}
				opd:command threshold {
					opd:help "Show sensor thresholds";
					opd:on-enter 'vyatta-show-sensors threshold';
				}
			}
		}
	}
}
