module vyatta-system-hardware-cpu-history-v1 {
	namespace "urn:vyatta.com:mgmt:vyatta-system-hardware-cpu-history:1";
	prefix vyatta-system-hardware-cpu-history-v1;

	import vyatta-system-v1 {
		prefix system;
	}
	import configd-v1 {
		prefix configd;
	}
	import vyatta-op-show-hardware-cpu-v1 {
		prefix show-hardware-cpu;
	}

	organization "AT&T Inc.";
	contact
		"AT&T
		 Postal: 208 S. Akard Street
				 Dallas, TX 75202
		 Web: www.att.com";

	description
		"Copyright (c) 2018-2019, AT&T Intellectual Property.
		 All rights reserved.

		 Redistribution and use in source and binary forms, with or without
		 modification, are permitted provided that the following conditions
		 are met:

		 1. Redistributions of source code must retain the above copyright
		    notice, this list of conditions and the following disclaimer.
		 2. Redistributions in binary form must reproduce the above
		    copyright notice, this list of conditions and the following
		    disclaimer in the documentation and/or other materials provided
		    with the distribution.
		 3. Neither the name of the copyright holder nor the names of its
		    contributors may be used to endorse or promote products derived
		    from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		Provides the config:false nodes within the main config tree for the
		show hardware cpu history operational CLI command.";

	revision 2018-05-31 {
		description "Initial version";
	}

	grouping cpu-utilization {
		description "Data nodes for Total CPU Usage History Statistics.";

		container cpu-history {
			if-feature show-hardware-cpu:cpu-history;
			description "The system-wide process CPU usage statistics.";
			config false;
			configd:get-state "vyatta-cpu-history-client"; 

			list cpu-data {
				description "The list of cpu averages from the device.";
				key "interval";
			
				leaf interval {
					description "The time interval in minutes for the entry";
					type uint16;
					units "minutes";
				}

				leaf user {
					description "The average CPU user usage percentage";
					type system:percent;
					units "percent";
				}

				leaf nice {
					description "The average CPU utilization with nice (lower scheduling) priority";
					type system:percent;
					units "percent";
				}

				leaf system {
					description "The average CPU system usage percentage";
					type system:percent;
					units "percent";
				}

				leaf iowait {
					description "The average CPU IOWait usage percentage";
					type system:percent;
					units "percent";
				}

				leaf steal {
					description "The average CPU steal usage percentage";
					type system:percent;
					units "percent";
				}

				leaf idle {
					description "The average idle CPU percentage";
					type system:percent;
					units "percent";
				}
			}
		}
	}
	augment /system:system {
		uses cpu-utilization;
	}
}
