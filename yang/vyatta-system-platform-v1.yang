module vyatta-system-platform-v1 {
    namespace "urn:vyatta.com:mgmt:vyatta-system-platform:1";
    prefix vyatta-system-platform-v1;

    import vyatta-system-v1 {
        prefix system;
    }
    import configd-v1 {
        prefix configd;
    }

    organization "AT&T Inc.";
    contact
        "AT&T
         Postal: 208 S. Akard Street
                 Dallas, TX 75202
         Web: www.att.com";

    description
        "Copyright (c) 2018-2019, AT&T Intellectual Property.
         All rights reserved.

         Redistribution and use in source and binary forms, with or without
         modification, are permitted provided that the following conditions
         are met:

         1. Redistributions of source code must retain the above copyright
            notice, this list of conditions and the following disclaimer.
         2. Redistributions in binary form must reproduce the above
            copyright notice, this list of conditions and the following
            disclaimer in the documentation and/or other materials provided
            with the distribution.
         3. Neither the name of the copyright holder nor the names of its
            contributors may be used to endorse or promote products derived
            from this software without specific prior written permission.

         THIS SOFTWARE IS PROVIDED BY THE COPYRIGHT HOLDERS AND CONTRIBUTORS
         'AS IS' AND ANY EXPRESS OR IMPLIED WARRANTIES, INCLUDING, BUT NOT
         LIMITED TO, THE IMPLIED WARRANTIES OF MERCHANTABILITY AND FITNESS
         FOR A PARTICULAR PURPOSE ARE DISCLAIMED. IN NO EVENT SHALL THE
         COPYRIGHT HOLDER OR CONTRIBUTORS BE LIABLE FOR ANY DIRECT, INDIRECT,
         INCIDENTAL, SPECIAL, EXEMPLARY, OR CONSEQUENTIAL DAMAGES (INCLUDING,
         BUT NOT LIMITED TO, PROCUREMENT OF SUBSTITUTE GOODS OR SERVICES;
         LOSS OF USE, DATA, OR PROFITS; OR BUSINESS INTERRUPTION) HOWEVER
         CAUSED AND ON ANY THEORY OF LIABILITY, WHETHER IN CONTRACT, STRICT
         LIABILITY, OR TORT (INCLUDING NEGLIGENCE OR OTHERWISE) ARISING IN
         ANY WAY OUT OF THE USE OF THIS SOFTWARE, EVEN IF ADVISED OF THE
         POSSIBILITY OF SUCH DAMAGE.

         SPDX-License-Identifier: BSD-3-Clause

         System platform configuration";

    revision 2018-03-10 {
         description "Initial version";
    }

	typedef platform-type {
			type enumeration {
                    enum "router" {
							configd:help "All interfaces isolated by default.";
							description "The platform is configured as a router. All interfaces are brought up
                                     isolated (i.e., in their own individual L2 domains) by default.";
                    }
                    enum "switch" {
							configd:help "Switch interfaces enslaved to hardware switches by default.";
							description "The platform is configured as a switch. Interfaces belonging to a
                                     hardware switch are automatically enslaved to the appropriate switch
                                     by default";
                    }
			}
	}

    augment /system:system {
        container platform {
            configd:help "Platform configuration parameters";
            description "Configuration parameters that affect overall platform behaviour";
            leaf type {
					type platform-type;
					configd:help "Platform type. Influences default interface state in the system.";
					configd:update "vyatta-platform --action=set --attr=platform-type --value=$VAR(@)";
					configd:delete "vyatta-platform --action=delete --attr=platform-type";
					description "This command provides an override for the overall platform behaviour.
                                 The system software is platform-independent and can run on a variety
                                 of underlying hardware. Some instantiations can be on hardware switches
                                 in which all interfaces belong to an L2 domain by default.
                                 Other instantiations of the same software can be in a virtual setup where
                                 there is no real hardware to manage and all interfaces are isolated by default.
                                 The default mode of operation of the platform is determined automatically
                                 based on hardware probing. This configuration element provides the user with
                                 the ability to override the discovered default.";
            }
        }
    }
}
