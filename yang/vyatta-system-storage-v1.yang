module vyatta-system-storage-v1 {
    namespace "urn:vyatta.com:mgmt:vyatta-system-storage:1";
    prefix vyatta-system-storage-v1;

    import vyatta-system-v1 {
        prefix system;
    }
    import configd-v1 {
        prefix configd;
    }

    organization "AT&T Inc.";
    contact
        "AT&T
         Postal: 208 S. Akard Street
                 Dallas, TX 75202
         Web: www.att.com";

    description
        "Copyright (c) 2020, AT&T Intellectual Property.
         All rights reserved.

         Redistribution and use in source and binary forms, with or without
         modification, are permitted provided that the following conditions
         are met:

         1. Redistributions of source code must retain the above copyright
            notice, this list of conditions and the following disclaimer.
         2. Redistributions in binary form must reproduce the above
            copyright notice, this list of conditions and the following
            disclaimer in the documentation and/or other materials provided
            with the distribution.
         3. Neither the name of the copyright holder nor the names of its
            contributors may be used to endorse or promote products derived
            from this software without specific prior written permission.

         THIS SOFTWARE IS PROVIDED BY THE COPYRIGHT HOLDERS AND CONTRIBUTORS
         'AS IS' AND ANY EXPRESS OR IMPLIED WARRANTIES, INCLUDING, BUT NOT
         LIMITED TO, THE IMPLIED WARRANTIES OF MERCHANTABILITY AND FITNESS
         FOR A PARTICULAR PURPOSE ARE DISCLAIMED. IN NO EVENT SHALL THE
         COPYRIGHT HOLDER OR CONTRIBUTORS BE LIABLE FOR ANY DIRECT, INDIRECT,
         INCIDENTAL, SPECIAL, EXEMPLARY, OR CONSEQUENTIAL DAMAGES (INCLUDING,
         BUT NOT LIMITED TO, PROCUREMENT OF SUBSTITUTE GOODS OR SERVICES;
         LOSS OF USE, DATA, OR PROFITS; OR BUSINESS INTERRUPTION) HOWEVER
         CAUSED AND ON ANY THEORY OF LIABILITY, WHETHER IN CONTRACT, STRICT
         LIABILITY, OR TORT (INCLUDING NEGLIGENCE OR OTHERWISE) ARISING IN
         ANY WAY OUT OF THE USE OF THIS SOFTWARE, EVEN IF ADVISED OF THE
         POSSIBILITY OF SUCH DAMAGE.

         SPDX-License-Identifier: BSD-3-Clause

         The YANG module for vyatta-system-storage-v1";

    revision 2020-11-18 {
        description "Initial revision of version 1.";
    }

    typedef scheduler-type {
        description
            "Scheduler for block devices.";

        type enumeration {
            enum deadline {
                description "deadline I/O scheduler";
                configd:help "deadline I/O scheduler";
            }
            enum none {
                description "no-op I/O scheduler";
                configd:help "no-op I/O scheduler";
            }
        }
    }

    typedef interval {
        description
            "Interval to discard unused blocks.";

        type enumeration {
            enum hourly {
                description "Hourly interval";
                configd:help "Hourly interval";
            }
            enum daily {
                description "Daily interval";
                configd:help "Daily interval";
            }
            enum weekly {
                description "Weekly interval";
                configd:help "Weekly interval";
            }
            enum monthly {
                description "Monthly interval";
                configd:help "Monthly interval";
            }
        }
    }

    augment /system:system {
        container storage {
            description "Filesystem configuration";
            configd:help "Filesystem configuration";
            configd:end "vyatta-block-device scheduler";
            list block-device {
                description "Block devices configuration";
                configd:help "Block device name";
                configd:allowed "vyatta-block-device list-block-devices";
                key "name";
                leaf name {
                    description "Block device name";
                    configd:help "Block device name";
                    type string;
                }
                leaf scheduler {
                    description "Block device scheduler";
                    configd:help "Block device scheduler";
                    type scheduler-type;
                }
                container discard-unused-blocks {
                    presence "Enable schedule to discard block-device's unused blocks";
                    description "Discard unused blocks";
                    configd:help "Discard unused blocks";
                    configd:end "vyatta-block-device discard-unused-blocks";
                    leaf repeat-interval {
                        description
                            "Repeat interval to discard unused blocks.
                             hourly : Discard blocks starting at the next hour.
                             daily  : Discard blocks daily at the specified start-time (default: 04:00:00).
                             weekly : Discard blocks every Sunday at the specified start-time (default: 04:00:00).
                             monthly: Discard blocks every 1st day of the month at the
                                      specified start-time (default: 04:00:00).";
                        configd:help "Repeat interval to discard unused blocks";
                        type interval;
                        mandatory true;
                    }
                    leaf start-time {
                        description
                            "Start time (local time) to discard block-device's unused blocks.
                             For hourly - discard blocks starting at the next hour.
                             For daily, weekly and monthly - discard blocks at 04:00:00 by default.
                             Otherwise use the specified start-time value.";
                        configd:help "Start time to discard block-device's unused blocks";
                        type string {
                            pattern '\d{2}:\d{2}(:\d{2})?';
                            configd:help "Time: <hh:mm:(ss)>";
                        }
                        default "04:00:00";
                        configd:validate "vyatta-block-device validate-time $VAR(@)";
                    }
                }
            }
        }
    }

    rpc get-block-device {
        description "Get the block device scheduler";
        configd:call-rpc 'vyatta-block-device get-block-devices';
        output {
            list block-device {
                description "List of block devices";
                key "name";
                leaf name {
                    description "Block device name";
                    type string;
                }
                leaf current-scheduler {
                    description "Current Block device scheduler";
                    type string;
                }
                leaf-list available-schedulers {
                    description "List of available block device schedulers";
                    type string;
                }
            }
        }
    }

    rpc clear-block-device-unused-blocks {
        description "Clears the specified block device's unused blocks";
        configd:call-rpc "vyatta-block-device clear-unused-blocks";
        input {
            leaf block-device {
                description "Block device name";
                mandatory true;
                type string;
            }
        }
        output {
            leaf output {
                description "Number of bytes trimmed";
                type string;
            }
        }
    }
}
